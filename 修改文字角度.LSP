(defun c:s_update_angle()
  (print "by Sun Kaidong")
  (setq obj (ssget))
  (setq n (sslength obj))
  (setq k 0)
  (while (< k n)
    (setq name (ssname obj k))
    (setq data (entget name))
    (setq data_type (assoc '0 data))
    (setq data_type (cdr data_type))
    (if (= data_type "TEXT")
      (progn
	(setq data_ang (assoc '50 data))
        (setq pt1 (getpoint "选择方向起点：\n"))
        ;;调整文字方向
        (setq pt2 (getpoint "选定方向终点：\n"))
        (setq x1 (car pt1))
        (setq y1 (nth 1 pt1))
        (setq x2 (car pt2))
        (setq y2 (nth 1 pt2))
        (setq ang (atan (/ (- y2 y1) (- x2 x1)))) 
	(setq new_ang (cons 50 ang))
	(setq data (subst new_ang data_ang data))
	(entmod data)
      )
    )
    (setq k (+ k 1))
  )
)
