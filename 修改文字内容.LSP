;;修改文字编号内容，如将QL1,QL2后的数字依次自增1，变成QL2,QL3
(print "使用命令: s_update_text ; writen by Sun Kaidong")

(defun c:s_update_text()
  (setq obj (ssget))
  (setq n (sslength obj))
  (setq k 0)
  (while (< k n)
    (setq name (ssname obj k))
    (setq data (entget name))
    (setq data_type (assoc '0 data))
    (setq data_type (cdr data_type))
    (if (= data_type "TEXT")
      (progn
	(setq data_cont (assoc '1 data))
	(setq content (cdr data_cont))
	;;获取字符串中的数字
	;(setq prefix (substr content 1 3))
	(setq prefix (vl-string-right-trim "0123456789" content))
	(setq len (strlen prefix))
	(setq len2 (- (strlen content) len))
	(setq count (atoi (substr content (+ 1 len) 3)))
	(setq count (itoa (+ count 1)))
        (cond
          ((= 2 (- len2 (strlen count))) (setq new_cont (strcat prefix "00" count)))
          ((= 1 (- len2 (strlen count))) (setq new_cont (strcat prefix "0" count)))
	  ((= 0 (- len2 (strlen count))) (setq new_cont (strcat prefix "" count)))
        )
	;(setq new_cont (strcat "TEMP" count))
	(setq new_cont_list (cons 1 new_cont))
	(setq data (subst new_cont_list data_cont data))
	(entmod data)
      )
    )
    (setq k (+ k 1))
  )
)
